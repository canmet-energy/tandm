FME workspace 3_KwH_GJ_Meter_to_Report_Aggregation.fmw

Parameters:
- SourceDataset_XLSXR = X:\Output\Reports\Gas_Electric_Meter_Output_Pre_Aggregation.xlsx   # Source Microsoft Excel File(s)
- DestDataset_XLSXW = X:\Output\Reports\Gas_Electric_Meter_FME_Aggregate_Report.xlsx   # Destination Microsoft Excel File

Readers:
- XLSXR_1: XLSXR from $(SourceDataset_XLSXR) in BCALB-83

Writers:
- XLSXW_1: XLSXW to $(DestDataset_XLSXW) in BCALB-83

Note: Electric_Meter_Output_Pre_Aggregation_[XLSXR]
DeliveryPoint_Meters/Table1 (reader XLSXR_1)
    attributes: OBJECTID number(6,0), METER_NUMBER number(8,0), CUST_CLASS char(2), DPOID number(7,0), DPSUBTYPECD number(2,0), DPSUBTYPE char(26), TRANSFORMEROBJECTID number(7,0), SERVICE_POINT_NUMBER number(11,0), ADDRESS char(41), EMAIL_ADDR char(97), LOCATION_DETAILS char(213), CONNECTIVITYCONFIRMEDDATE number(6,0), USAGEDATE date, ENDTIME number(17,10), KWH_USAGE number(9,4), KVAH_USAGE number(9,4), KVAH_DERIVED char(2), PFACTOR number(5,2), FABRIC_ID number(6,0), AFP_OID number(12,0), JUROL number(12,0), JURISDICTI number(4,0), JUR_NEIGH number(7,0), CREATDATE datetime, EFFECDATE datetime, EXPIRY_DAT string, PHOTO_LINK string, AREANAME number(3,0), SOURCE_ORI char(6), LOCALAREA char(16),
      SHP_Length number(19,13), SHP_Area number(20,12), Major_Category char(35), Category char(33), Sub_Category char(43), Vintage char(15), CEEMap_Archetype char(20), BCBCOccupancy char(21), Part3_Part9 char(11), CT number(11,2), Neighbourhood char(18), Municipality char(16), RegionalDistrict char(38), CEEMap_Ins string, CEEMap_Dwe char(18), CEEMap_Nos number(4,0), CEEMap_overlaps number(2,0), USAGE kWh number(8,0), Reclassified char(2), Original_Major_Category char(35), Original_Category char(33), Original_Sub_Category char(43), Original_Vintage char(15), Original_Neighbourhood char(18), Notes char(33)
    -> AttributeRenamer_USAGE
Note: Gas_Electric_Meter_Output_Pre_Aggregation [XLSXR]
Gas_Meters/Table4 (reader XLSXR_1)
    attributes: OBJECTID number(6,0), Meter_dcrs_id string, Meter_sworld_id number(10,0), Meter_Number char(11), Meter_Service_Type char(10), Meter_X x_coordinate, Meter_Y y_coordinate, Meter_DPt_sworld_id number(10,0), Meter_Asset_id string, Meter_Status char(10), Meter_Critical_Customer_YN char(4), Meter_Type string, Meter_Installation_Date string, Addr_Unit_Number char(9), Addr_Civic_Number char(5), Addr_Street_Direction_Suffix char(2), Addr_Street_Direction_Prefix boolean, Addr_Street_Name char(17), Addr_Street_Suffix_Type char(10), Addr_Postal_Code char(8), Addr_CIS_Town char(9), Addr_POD number(9,0), Addr_Premise_Num number(9,0), FABRIC_ID number(6,0), AFP_OID number(12,0), JUROL number(12,0), JURISDICTI number(4,0), JUR_NEIGH number(7,0), CREATDATE datetime, EFFECDATE datetime,
      EXPIRY_DAT string, PHOTO_LINK string, AREANAME number(3,0), SOURCE_ORI char(6), LOCALAREA char(16), SHP_Length number(19,13), SHP_Area number(20,12), Major_Category char(35), Category char(33), Sub_Category char(43), Vintage char(15), CEEMap_Archetype char(20), BCBCOccupancy char(21), Part3_Part9 char(11), CT number(11,2), Neighbourhood char(18), Municipality char(16), RegionalDistrict char(38), CEEMap_Ins char(37), CEEMap_Dwe char(26), CEEMap_Nos number(4,0), CEEMap_overlaps number(2,0), CITY char(9), RATE char(7), POD number(9,0), GJs number(11,4), Reclassified char(2), Original_Major_Category char(35), Original_Category char(33), Original_Sub_Category char(43),
      Original_Neighbourhood char(17), Notes char(25), Original_Vintage char(15)
    -> AttributeRenamer_GJs

Bookmark: Attribute Settings
AttributeRenamer_USAGE
    ATTR_TABLE = RENAME_SET_DEFAULT USAGE kWh > Electricity_kWh
    MISSING_INPUT_ATTRS = REMOVE
    -> AttributeCreator_Total_Count_e_meters
AttributeCreator_Total_Count_e_meters
    ATTR_TABLE = SET_TO Total Count = 1
    -> Aggregator_MC_Vintage_kWh
    -> Aggregator_MC_Cat_SC_Vintage_kWh
    -> Aggregator_MC_Vintage_kWh_3
    -> Aggregator_BCBC_O_Vintage_kWh
    -> Aggregator_NBhood_Major_Category
    -> Aggregator_MC_Vintage_kWh_6

Bookmark: New Bookmark
Aggregator_MC_Vintage_kWh
    ACCUM_ATTRS_NAME = Merge Incoming Attributes
    GROUP_BY = Major_Category Vintage
    MODE = Attributes Only
    SEP = ,
    SUM = "Total Count" Electricity_kWh
    AGGREGATE -> Electric_ER_1 (writer XLSXW_1)
Aggregator_MC_Cat_SC_Vintage_kWh
    ACCUM_ATTRS_NAME = Merge Incoming Attributes
    GROUP_BY = Major_Category Category Sub_Category Vintage
    MODE = Attributes Only
    SEP = ,
    SUM = "Total Count" Electricity_kWh
    AGGREGATE -> Electric_ER_2 (writer XLSXW_1)
Aggregator_MC_Vintage_kWh_3
    ACCUM_ATTRS_NAME = Merge Incoming Attributes
    GROUP_BY = Vintage Part3_Part9
    MODE = Attributes Only
    SEP = ,
    SUM = "Total Count" Electricity_kWh
    AGGREGATE -> Electric_ER_3 (writer XLSXW_1)
Aggregator_BCBC_O_Vintage_kWh
    ACCUM_ATTRS_NAME = Merge Incoming Attributes
    GROUP_BY = BCBCOccupancy Vintage
    MODE = Attributes Only
    SEP = ,
    SUM = "Total Count" Electricity_kWh
    AGGREGATE -> Electric_ER_4 (writer XLSXW_1)
Aggregator_NBhood_Major_Category
    ACCUM_ATTRS_NAME = Merge Incoming Attributes
    GROUP_BY = Neighbourhood Major_Category
    MODE = Attributes Only
    SEP = ,
    SUM = "Total Count" Electricity_kWh
    AGGREGATE -> Electric_ER_5 (writer XLSXW_1)
Aggregator_MC_Vintage_kWh_6
    ACCUM_ATTRS_NAME = Merge Incoming Attributes
    GROUP_BY = CT Major_Category
    MODE = Attributes Only
    SEP = ,
    SUM = "Total Count" Electricity_kWh
    AGGREGATE -> Electric_ER_6 (writer XLSXW_1)

Bookmark: Electric Energy Reports all reports are in XLSX format
Electric_ER_1 (writer XLSXW_1)
    attributes: Major_Category string(254), Vintage string(254), Electricity_kWh string(254), Total Count number(10)
Electric_ER_2 (writer XLSXW_1)
    attributes: Major_Category string(254), Category string(254), Sub_Category string(254), Vintage string(254), Electricity_kWh string(254), Total Count number(10)
Electric_ER_3 (writer XLSXW_1)
    attributes: Part3_Part9 string(254), Vintage string(254), Electricity_kWh string(254), Total Count number(10)
Electric_ER_4 (writer XLSXW_1)
    attributes: BCBCOccupancy string(254), Vintage string(254), Electricity_kWh string(254), Total Count number(10)
Electric_ER_5 (writer XLSXW_1)
    attributes: Neighbourhood string(254), Major_Category string(254), Electricity_kWh string(254), Total Count number(10)
Electric_ER_6 (writer XLSXW_1)
    attributes: CT string(254), Major_Category string(254), Electricity_kWh string(254), Total Count number(10)

Bookmark: Attribute Settings
AttributeRenamer_GJs
    ATTR_TABLE = RENAME_SET_DEFAULT GJs > Natural _Gas_GJs
    MISSING_INPUT_ATTRS = REMOVE
    -> AttributeCreator_Total_Count_Nat_Gas_Meters
AttributeCreator_Total_Count_Nat_Gas_Meters
    ATTR_TABLE = SET_TO Total Count = 1
    -> Aggregator_MC_Vintage_Gj
    -> Aggregator_MC_Vintage_Gj_2
    -> Aggregator_MC_Vintage_Gj_3
    -> Aggregator_MC_Vintage_Gj_4
    -> Aggregator_MC_Vintage_Gj_5
    -> Aggregator_MC_Vintage_Gj_6

Bookmark: Gas Report Aggregators
Aggregator_MC_Vintage_Gj
    ACCUM_ATTRS_NAME = Merge Incoming Attributes
    GROUP_BY = Major_Category Vintage
    MODE = Attributes Only
    SEP = ,
    SUM = "Total Count" "Natural _Gas_GJs"
    AGGREGATE -> Gas_ER_1 (writer XLSXW_1)
Aggregator_MC_Vintage_Gj_2
    ACCUM_ATTRS_NAME = Merge Incoming Attributes
    GROUP_BY = Major_Category Category Sub_Category Vintage
    MODE = Attributes Only
    SEP = ,
    SUM = "Total Count" "Natural _Gas_GJs"
    AGGREGATE -> Gas_ER_2 (writer XLSXW_1)
Aggregator_MC_Vintage_Gj_3
    ACCUM_ATTRS_NAME = Merge Incoming Attributes
    GROUP_BY = Part3_Part9 Vintage
    MODE = Attributes Only
    SEP = ,
    SUM = "Total Count" "Natural _Gas_GJs"
    AGGREGATE -> Gas_ER_3 (writer XLSXW_1)
Aggregator_MC_Vintage_Gj_4
    ACCUM_ATTRS_NAME = Merge Incoming Attributes
    GROUP_BY = BCBCOccupancy Vintage
    MODE = Attributes Only
    SEP = ,
    SUM = "Total Count" "Natural _Gas_GJs"
    AGGREGATE -> Gas_ER_4 (writer XLSXW_1)
Aggregator_MC_Vintage_Gj_5
    ACCUM_ATTRS_NAME = Merge Incoming Attributes
    GROUP_BY = Neighbourhood Major_Category
    MODE = Attributes Only
    SEP = ,
    SUM = "Total Count" "Natural _Gas_GJs"
    AGGREGATE -> Gas_ER_5 (writer XLSXW_1)
Aggregator_MC_Vintage_Gj_6
    ACCUM_ATTRS_NAME = Merge Incoming Attributes
    GROUP_BY = CT Major_Category
    MODE = Attributes Only
    SEP = ,
    SUM = "Total Count" "Natural _Gas_GJs"
    AGGREGATE -> Gas_ER_6 (writer XLSXW_1)

Bookmark: Gas Energy Reports
Gas_ER_1 (writer XLSXW_1)
    attributes: Major_Category string(254), Vintage string(254), Natural _Gas_GJs number(20), Total Count number(20)
Gas_ER_2 (writer XLSXW_1)
    attributes: Major_Category string(254), Category string(254), Sub_Category string(254), Vintage string(254), Natural _Gas_GJs number(20), Total Count number(20)
Gas_ER_3 (writer XLSXW_1)
    attributes: Part3_Part9 string(254), Vintage string(254), Natural _Gas_GJs number(20), Total Count number(20)
Gas_ER_4 (writer XLSXW_1)
    attributes: BCBCOccupancy string(254), Vintage string(254), Natural _Gas_GJs number(20), Total Count number(20)
Gas_ER_5 (writer XLSXW_1)
    attributes: Neighbourhood string(254), Major_Category string(254), Natural _Gas_GJs number(20), Total Count number(20)
Gas_ER_6 (writer XLSXW_1)
    attributes: CT string(254), Major_Category string(254), Natural _Gas_GJs number(20), Total Count number(20)

Bookmark: All Gas Attributes
Gas_ER_00 (writer XLSXW_1) [off]
    attributes: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
