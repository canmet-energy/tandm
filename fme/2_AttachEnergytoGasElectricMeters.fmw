FME workspace 2_AttachEnergytoGasElectricMeters.fmw

Parameters:
- SourceDataset_FBC_Electric_kWh_CSV = X:\From_Billing\KEL_Electricity_Consumption_2021\FBC_Electric_Meters_Results_KEL.csv   # Source CSV (Comma Separated Value) File(s)
- SourceDataset_GAS_POD_GJ_CSV = X:\From_Billing\KEL_Natural_Gas_Consumption_by_POD_2021\KelownaFlatFile.csv   # Source CSV (Comma Separated Value) File(s)
- SourceDataset_GEODATABASE_FILE = X:\Intermediate Data\TaNDM_Project_Intermediate_BIR_Stage_10.gdb   # Source File Geodatabase
- DestDataset_GEODATABASE_FILE = X:\Intermediate Data\TaNDM_Project_Intermediate_BIR_Stage_11.gdb   # Destination File Geodatabase

Readers:
- GEODATABASE_FILE_1: GEODATABASE_FILE from $(SourceDataset_GEODATABASE_FILE) in BCALB-83
- CSV2_2: CSV2 from $(SourceDataset_GAS_POD_GJ_CSV)
- CSV2_1: CSV2 from $(SourceDataset_FBC_Electric_kWh_CSV)

Writers:
- GEODATABASE_FILE_2: GEODATABASE_FILE to $(DestDataset_GEODATABASE_FILE) in BCALB-83

Bookmark: Electric
DeliveryPoint_Meters_matched (reader GEODATABASE_FILE_1)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double, AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double, SHP_Area double, Major_Category char(254), Category char(254), Sub_Category char(254), Vintage char(254), CEEMap_Archetype char(254), BCBCOccupancy char(254), Part3_Part9 char(254), CT char(254), Neighbourhood char(254), Municipality char(254), RegionalDistrict char(254)
    -> FeatureMerger_2 [REQUESTOR]
Note: CSV: FBC_Electric_Meters_Results_KEL [CSV2]
CSV (reader CSV2_1)
    attributes: METER_NUMBER uint32, USAGE uint32
    -> DuplicateFilter_Electric
DuplicateFilter_Electric
    INPUT_ORDERED_CHOICE = No
    KEYATTR = METER_NUMBER USAGE
    UNIQUE -> AttributeRenamer_2
    DUPLICATE -> Duplicate_FBC_kWh_Suppliers (writer GEODATABASE_FILE_2)
AttributeRenamer_2
    ATTR_TABLE = RENAME_SET_DEFAULT METER_NUMBER > METER
    MISSING_INPUT_ATTRS = REMOVE
    -> FeatureMerger_2 [SUPPLIER]
FeatureMerger_2
    ATTR_ACCUM_MODE = Merge Supplier
    ATTR_CONFLICT_RES = Use Requestor
    IGNORE_NULLS = No
    JOIN_KEYS = @Value(METER_NUMBER) @Value(METER) AUTO
    MERGE_TYPE = Attributes and Geometry
    PROCESS_DUPS = NO
    REJECT_NULL_MISSING_KEYS = No
    SUPPLIERS_FIRST = No
    MERGED -> DeliveryPoint_Meters_matched_with_kWh (writer GEODATABASE_FILE_2)
    UNMERGED_REQUESTOR -> DeliveryPoint_Meters_matched_without_kWh (writer GEODATABASE_FILE_2)
    USED_SUPPLIER -> ELECTRIC_Used_Supplier (writer GEODATABASE_FILE_2)
    UNUSED_SUPPLIER -> ELECTRIC_Unused_Supplier (writer GEODATABASE_FILE_2)
DeliveryPoint_Meters_matched_with_kWh (writer GEODATABASE_FILE_2)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double, AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), USAGE char(254)
DeliveryPoint_Meters_matched_without_kWh (writer GEODATABASE_FILE_2)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double, AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), USAGE char(254)
ELECTRIC_Used_Supplier (writer GEODATABASE_FILE_2)
    attributes: METER integer, USAGE integer
ELECTRIC_Unused_Supplier (writer GEODATABASE_FILE_2)
    attributes: METER integer, USAGE integer
Duplicate_FBC_kWh_Suppliers (writer GEODATABASE_FILE_2)
    attributes: METER_NUMBER double, USAGE double

Bookmark: GAS
Gas_Meters_matched (reader GEODATABASE_FILE_1)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254)
    -> FeatureMerger [REQUESTOR]
Note: GAS_CONSUMPTION_CSV: KelownaFlatFile [CSV2]
CSV (reader CSV2_2)
    attributes: CITY varchar(8), RATE varchar(6), POD uint32, YEAR uint32, Total_GJs real64
    -> DuplicateFilter_Gas
DuplicateFilter_Gas
    INPUT_ORDERED_CHOICE = No
    KEYATTR = CITY POD RATE Total_GJs YEAR
    UNIQUE -> AttributeRenamer
    DUPLICATE -> Duplicate_Gas_POD_Gjs_Suppliers (writer GEODATABASE_FILE_2)
AttributeRenamer
    ATTR_TABLE = RENAME_SET_DEFAULT Total_GJs > GJs
    MISSING_INPUT_ATTRS = REMOVE
    -> FeatureMerger [SUPPLIER]
FeatureMerger
    ATTR_ACCUM_MODE = Merge Supplier
    ATTR_CONFLICT_RES = Use Requestor
    IGNORE_NULLS = No
    JOIN_KEYS = @Value(Addr_POD) @Value(POD) AUTO
    MERGE_TYPE = Attributes Only
    PROCESS_DUPS = NO
    REJECT_NULL_MISSING_KEYS = No
    SUPPLIERS_FIRST = No
    MERGED -> DuplicateFilter_3
    UNMERGED_REQUESTOR -> AttributeFilter
    USED_SUPPLIER -> GAS_Used_Supplier (writer GEODATABASE_FILE_2)
    UNUSED_SUPPLIER -> GAS_Unused_Supplier (writer GEODATABASE_FILE_2)
DuplicateFilter_3
    INPUT_ORDERED_CHOICE = No
    KEYATTR = POD
    UNIQUE -> Gas_Meters_matched_with_Gjs (writer GEODATABASE_FILE_2)
    DUPLICATE -> Gas_Meters_matched_with_Gjs_Duplicate_POD (writer GEODATABASE_FILE_2)
Gas_Meters_matched_with_Gjs (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CITY char(50), RATE char(20), POD char(32), GJs double
Gas_Meters_matched_with_Gjs_Duplicate_POD (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CITY char(50), RATE char(20), POD char(32), GJs double
AttributeFilter
    ATTR_NAME = Meter_Status
    ATTR_VALUES = <Empty>,<Missing>,<Null>,<Unfiltered>,Abandoned,Existing,Proposed
    Abandoned -> Gas_Meters_ABANDONED_matched_without_Gjs (writer GEODATABASE_FILE_2)
    Existing -> Gas_Meters_EXISTING_matched_without_Gjs (writer GEODATABASE_FILE_2)
    Proposed -> Gas_Meters_PROPOSED_matched_without_Gjs (writer GEODATABASE_FILE_2)
Gas_Meters_ABANDONED_matched_without_Gjs (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CITY char(50), RATE char(20), POD char(32), GJs double
Gas_Meters_EXISTING_matched_without_Gjs (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CITY char(50), RATE char(20), POD char(32), GJs double
Gas_Meters_PROPOSED_matched_without_Gjs (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CITY char(50), RATE char(20), POD char(32), GJs double
GAS_Used_Supplier (writer GEODATABASE_FILE_2)
    attributes: CITY char(8), RATE char(6), POD double, YEAR double, GJs double
GAS_Unused_Supplier (writer GEODATABASE_FILE_2)
    attributes: CITY char(8), RATE char(6), POD double, YEAR double, GJs double
Duplicate_Gas_POD_Gjs_Suppliers (writer GEODATABASE_FILE_2)
    attributes: CITY char(8), RATE char(6), POD double, YEAR double, Total_GJs double
