FME workspace 4_CEEMap_Dwellings_Attached_to_Meters.fmw

Parameters:
- SourceDataset_SHAPEFILE = X:\External Data\KEL_FABRIC_FLAT_CEEMAP\KEL_FABRIC_FLAT_CEEMAP.shp   # Source Esri Shapefile(s)
- SourceDataset_GEODATABASE_FILE = X:\Intermediate Data\TaNDM_Project_Intermediate_BIR_Stage_11.gdb   # Source File Geodatabase
- DestDataset_GEODATABASE_FILE = X:\Intermediate Data\TaNDM_Project_Intermediate_BIR_Stage_12.gdb   # Destination File Geodatabase
- DestDataset_XLSXW = X:\Output\Gas_Electric_Meter_Output.xlsx   # Destination Microsoft Excel File

Readers:
- GEODATABASE_FILE_1: GEODATABASE_FILE from $(SourceDataset_GEODATABASE_FILE) in BCALB-83
- SHAPEFILE_1: SHAPEFILE from $(SourceDataset_SHAPEFILE) in BCALB-83

Writers:
- GEODATABASE_FILE_2: GEODATABASE_FILE to $(DestDataset_GEODATABASE_FILE) in BCALB-83
- XLSXW_1: XLSXW to $(DestDataset_XLSXW) in BCALB-83

Note: DeliveryPoint_Meters_matched_with_kWh [GEODATABASE_FILE]
DeliveryPoint_Meters_matched_with_kWh (reader GEODATABASE_FILE_1)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double, AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), USAGE char(254)
    -> PointOnAreaOverlayer_ELECTRIC_METERS [POINT]
Note: KEL_FABRIC_FLAT_CEEMAP [SHAPEFILE]
KEL_FABRIC_FLAT_CEEMAP (reader SHAPEFILE_1)
    attributes: OBJECTID number(11,0), FABRIC_ID number(11,0), AFP_OID varchar(30), JUROL varchar(30), JURISDICTI varchar(50), JUR_NEIGH varchar(50), CREATDATE varchar(21), EFFECDATE varchar(21), EXPIRY_DAT varchar(21), PHOTO_LINK varchar(254), AREANAME varchar(50), SOURCE_ORI varchar(50), LOCALAREA varchar(50), SHP_Length number(31,15), SHP_Area number(31,15), CEEMap_Ins varchar(254), CEEMap_Dwe varchar(254), CEEMap_Nos varchar(254)
    -> PointOnAreaOverlayer_GAS_METERS [AREA]
    -> PointOnAreaOverlayer_ELECTRIC_METERS [AREA]
PointOnAreaOverlayer_ELECTRIC_METERS
    ATTR_ACCUM_MODE = Merge Incoming
    ATTR_CONFLICT_RES = Use Original
    DEAGGREGATE_INPUT = Yes
    OV_ATTR = CEEMap_overlaps
    POLYS_FIRST = NO
    POINT -> DeliveryPoint_Meters_matched_with_kWh_CEE_Map (writer GEODATABASE_FILE_2)
    POINT -> DeliveryPoint_Meters (writer XLSXW_1)
Note: [XLSXW]
DeliveryPoint_Meters (writer XLSXW_1)
    attributes: OBJECTID number(20), METER_NUMBER string(11), CUST_CLASS string(1), DPOID number(20), DPSUBTYPECD number(20), DPSUBTYPE string(40), TRANSFORMEROBJECTID number(20), SERVICE_POINT_NUMBER number(20), ADDRESS string(40), EMAIL_ADDR string(100), LOCATION_DETAILS string(228), CONNECTIVITYCONFIRMEDDATE datetime(20), USAGEDATE number(20), ENDTIME datetime(20), KWH_USAGE number(20), KVAH_USAGE number(20), KVAH_DERIVED string(1), PFACTOR number(20), FABRIC_ID number(20), AFP_OID string(30), JUROL string(30), JURISDICTI string(50), JUR_NEIGH string(50), CREATDATE string(21), EFFECDATE string(21), EXPIRY_DAT string(21), PHOTO_LINK string(254), AREANAME string(50), SOURCE_ORI string(50), LOCALAREA string(50),
      SHP_Length number(20), SHP_Area number(20), Major_Category string(254), Category string(254), Sub_Category string(254), Vintage string(254), CEEMap_Archetype string(254), BCBCOccupancy string(254), Part3_Part9 string(254), CT string(254), Neighbourhood string(254), Municipality string(254), RegionalDistrict string(254), CEEMap_Ins string(254), CEEMap_Dwe string(254), CEEMap_Nos string(254), CEEMap_overlaps number(20), USAGE string(254)
Note: [GEODATABASE_FILE]
DeliveryPoint_Meters_matched_with_kWh_CEE_Map (writer GEODATABASE_FILE_2)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double, AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CEEMap_Ins char(254), CEEMap_Dwe char(254), CEEMap_Nos char(254), CEEMap_overlaps integer, USAGE char(254)
Note: Gas_Meters_matched_with_Gjs [GEODATABASE_FILE]
Gas_Meters_matched_with_Gjs (reader GEODATABASE_FILE_1)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CITY char(50), RATE char(20), POD char(32), GJs double
    -> PointOnAreaOverlayer_GAS_METERS [POINT]
PointOnAreaOverlayer_GAS_METERS
    ATTR_ACCUM_MODE = Merge Incoming
    ATTR_CONFLICT_RES = Use Original
    DEAGGREGATE_INPUT = Yes
    OV_ATTR = CEEMap_overlaps
    POLYS_FIRST = NO
    POINT -> Gas_Meters_matched_with_Gjs_CEEMap (writer GEODATABASE_FILE_2)
    POINT -> Gas_Meters (writer XLSXW_1)
Note: [XLSXW]
Gas_Meters (writer XLSXW_1)
    attributes: OBJECTID number(20), Meter_dcrs_id number(20), Meter_sworld_id number(20), Meter_Number string(20), Meter_Service_Type string(9), Meter_X string(20), Meter_Y string(32), Meter_DPt_sworld_id number(20), Meter_Asset_id string(36), Meter_Status string(16), Meter_Critical_Customer_YN string(3), Meter_Type string(20), Meter_Installation_Date string(8), Addr_Unit_Number string(32), Addr_Civic_Number string(32), Addr_Street_Direction_Suffix string(32), Addr_Street_Direction_Prefix string(32), Addr_Street_Name string(50), Addr_Street_Suffix_Type string(32), Addr_Postal_Code string(32), Addr_CIS_Town string(32), Addr_POD string(32), Addr_Premise_Num string(32), FABRIC_ID number(20), AFP_OID string(30), JUROL string(30), JURISDICTI string(50), JUR_NEIGH string(50), CREATDATE string(21), EFFECDATE string(21),
      EXPIRY_DAT string(21), PHOTO_LINK string(254), AREANAME string(50), SOURCE_ORI string(50), LOCALAREA string(50), SHP_Length number(20), SHP_Area number(20), Major_Category string(254), Category string(254), Sub_Category string(254), Vintage string(254), CEEMap_Archetype string(254), BCBCOccupancy string(254), Part3_Part9 string(254), CT string(254), Neighbourhood string(254), Municipality string(254), RegionalDistrict string(254), CEEMap_Ins string(254), CEEMap_Dwe string(254), CEEMap_Nos string(254), CEEMap_overlaps number(20), CITY string(50), RATE string(20), POD string(32), GJs number(20)
Note: [GEODATABASE_FILE]
Gas_Meters_matched_with_Gjs_CEEMap (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double, AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double, SHP_Area double, Major_Category char(254), Category char(254), Sub_Category char(254), Vintage char(254), CEEMap_Archetype char(254), BCBCOccupancy char(254), Part3_Part9 char(254), CT char(254), Neighbourhood char(254), Municipality char(254), RegionalDistrict char(254), CEEMap_Ins char(254), CEEMap_Dwe char(254), CEEMap_Nos char(254), CEEMap_overlaps integer, CITY char(50), RATE char(20), POD char(32), GJs double
