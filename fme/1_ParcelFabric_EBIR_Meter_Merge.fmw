FME workspace 1_ParcelFabric_EBIR_Meter_Merge.fmw

Parameters:
- SourceDataset_SHAPEFILE = X:\Kelowna_BIR_Enhanced_Flattened.shp   # Source Esri Shapefile(s)
- SourceDataset_GEODATABASE_FILE = X:\FBC Data\Meter_Complex_KEL.gdb   # File Geodatabase
- DestDataset_GEODATABASE_FILE = X:\Intermediate Data\TaNDM_Project_Intermediate_BIR_Stage_10.gdb   # File Geodatabase
- SourceDataset_GEODATABASE_FILE_2 = X:\FBC Data\Electric_Meters_KEL.gdb   # File Geodatabase

Readers:
- SHAPEFILE_1: SHAPEFILE from $(SourceDataset_SHAPEFILE) in BCALB-83
- GEODATABASE_FILE_1: GEODATABASE_FILE from $(SourceDataset_GEODATABASE_FILE) in BCALB-83
- GEODATABASE_FILE_3: GEODATABASE_FILE from $(SourceDataset_GEODATABASE_FILE_2) in SPHERICAL_MERCATOR

Writers:
- GEODATABASE_FILE_2: GEODATABASE_FILE to $(DestDataset_GEODATABASE_FILE) in BCALB-83

Note: Natural Gas Meters_KEL [GEODATABASE_FILE] / point geometry
meter (reader GEODATABASE_FILE_1)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32)
    -> PointOnAreaOverlayer_GAS_METERS [POINT]
Note: Kelowna_BIR_Enhanced_Flattened Assessment Fabric [SHAPEFILE] / polygon geometry
240202_Kelowna_BIR_Enhanced_Flattened (reader SHAPEFILE_1)
    attributes: OBJECTID number(11,0), FABRIC_ID number(11,0), AFP_OID varchar(30), JUROL varchar(30), JURISDICTI varchar(50), JUR_NEIGH varchar(50), CREATDATE varchar(21), EFFECDATE varchar(21), EXPIRY_DAT varchar(21), PHOTO_LINK varchar(254), AREANAME varchar(50), SOURCE_ORI varchar(50), LOCALAREA varchar(50), SHP_Length number(31,15), SHP_Area number(31,15), 240202 Cat varchar(254), 240202 C_1 varchar(254), 240202 C_2 varchar(254), 240202 C_3 varchar(254), 240202 C_4 varchar(254), 240202 C_5 varchar(254), 240202 C_6 varchar(254), 240202 C_7 varchar(254), 240202 C_8 varchar(254), 240202 C_9 varchar(254), 240202 C10 varchar(254)
    -> AttributeRenamer
AttributeRenamer
    ATTR_TABLE:
      RENAME_SET_DEFAULT 240202 Cat > Major_Category
      RENAME_SET_DEFAULT 240202 C_1 > Category
      RENAME_SET_DEFAULT 240202 C_2 > Sub_Category
      RENAME_SET_DEFAULT 240202 C_3 > Vintage
      RENAME_SET_DEFAULT 240202 C_4 > CEEMap_Archetype
      RENAME_SET_DEFAULT 240202 C_5 > BCBCOccupancy
      RENAME_SET_DEFAULT 240202 C_6 > Part3_Part9
      RENAME_SET_DEFAULT 240202 C_7 > CT
      RENAME_SET_DEFAULT 240202 C_8 > Neighbourhood
      RENAME_SET_DEFAULT 240202 C_9 > Municipality
      RENAME_SET_DEFAULT 240202 C10 > RegionalDistrict
    MISSING_INPUT_ATTRS = REMOVE
    -> PointOnAreaOverlayer_GAS_METERS [AREA]
    -> PointOnAreaOverlayer_ELECTRIC_METERS [AREA]
Note: PointOnAreaOverlayer_GAS_METERS [PointOnAreaOverlayer] / General: / Areas First: No / Aggregate Handling: Deaggregate / Attribute Accumulation: / Merge Attributes: / Accumulation Mode: Merge Incoming / Conflict Resolution: Use Original / Output Attribute Name: / Overlap Count: _overlaps
PointOnAreaOverlayer_GAS_METERS
    ATTR_ACCUM_MODE = Merge Incoming
    ATTR_CONFLICT_RES = Use Original
    DEAGGREGATE_INPUT = Yes
    OV_ATTR = _overlaps
    POLYS_FIRST = NO
    POINT -> OverlapTester_GAS_METERS
OverlapTester_GAS_METERS: Tester
    BOOL_OP = OR
    TEST_CLAUSE = TEST @Value(_overlaps) >= 1
    TEST_MODE = TEST
    PASSED -> Gas_Meters_matched (writer GEODATABASE_FILE_2)
    FAILED -> Gas_Meters_unmatched (writer GEODATABASE_FILE_2)
Note: gas meters inside parcel layer
Note: Gas_Meters_matched: / [GEODATABASE_FILE]
Gas_Meters_matched (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double(11,0), AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double(31,15), SHP_Area double(31,15), Major_Category char(254), Category char(254), Sub_Category char(254), Vintage char(254), CEEMap_Archetype char(254), BCBCOccupancy char(254), Part3_Part9 char(254), CT char(254), Neighbourhood char(254), Municipality char(254), RegionalDistrict char(254)
Note: gas meters outside parcel layer
Note: Gas_Meters_unmatched / [GEODATABASE_FILE]
Gas_Meters_unmatched (writer GEODATABASE_FILE_2)
    attributes: OBJECTID integer, Meter_dcrs_id integer, Meter_sworld_id integer, Meter_Number char(20), Meter_Service_Type char(9), Meter_X char(20), Meter_Y char(32), Meter_DPt_sworld_id integer, Meter_Asset_id char(36), Meter_Status char(16), Meter_Critical_Customer_YN char(3), Meter_Type char(20), Meter_Installation_Date char(8), Addr_Unit_Number char(32), Addr_Civic_Number char(32), Addr_Street_Direction_Suffix char(32), Addr_Street_Direction_Prefix char(32), Addr_Street_Name char(50), Addr_Street_Suffix_Type char(32), Addr_Postal_Code char(32), Addr_CIS_Town char(32), Addr_POD char(32), Addr_Premise_Num char(32), FABRIC_ID double(11,0), AFP_OID char(30), JUROL char(30), JURISDICTI char(50), JUR_NEIGH char(50), CREATDATE char(21), EFFECDATE char(21),
      EXPIRY_DAT char(21), PHOTO_LINK char(254), AREANAME char(50), SOURCE_ORI char(50), LOCALAREA char(50), SHP_Length double(31,15), SHP_Area double(31,15), Major_Category char(254), Category char(254), Sub_Category char(254), Vintage char(254), CEEMap_Archetype char(254), BCBCOccupancy char(254), Part3_Part9 char(254), CT char(254), Neighbourhood char(254), Municipality char(254), RegionalDistrict char(254)
Note: Electric_Meters_KEL [GEODATABASE_FILE] / point geometry
DeliveryPoint_Meters (reader GEODATABASE_FILE_3)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float
    -> Reprojector
Reprojector
    DEST = BCALB-83
    INTERPOLATION_TYPE_NAME = Nearest Neighbor
    RASTER_CELL_SIZE = Preserve Cells
    RASTER_TOLERANCE = 0.0
    SOURCE = SPHERICAL_MERCATOR
    REPROJECTED -> PointOnAreaOverlayer_ELECTRIC_METERS [POINT]
Note: PointOnAreaOverlayer_ELECTRIC_METERS [PointOnAreaOverlayer] / General: / Areas First: No / Aggregate Handling: Deaggregate / Attribute Accumulation: / Merge Attributes: / Accumulation Mode: Merge Incoming / Conflict Resolution: Use Original / Output Attribute Name: / Overlap Count: _overlaps
PointOnAreaOverlayer_ELECTRIC_METERS
    ATTR_ACCUM_MODE = Merge Incoming
    ATTR_CONFLICT_RES = Use Original
    DEAGGREGATE_INPUT = Yes
    OV_ATTR = _overlaps
    POLYS_FIRST = NO
    POINT -> OverlapTester_ELECTRIC_METERS
OverlapTester_ELECTRIC_METERS: Tester
    BOOL_OP = OR
    TEST_CLAUSE = TEST @Value(_overlaps) >= 1
    TEST_MODE = TEST
    PASSED -> DeliveryPoint_Meters_matched (writer GEODATABASE_FILE_2)
    FAILED -> DeliveryPoint_Meters_unmatched (writer GEODATABASE_FILE_2)
Note: electric meters inside parcel layer
Note: DeliveryPoint_Meters_matched [GEODATABASE_FILE]
DeliveryPoint_Meters_matched (writer GEODATABASE_FILE_2)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double(11,0), AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double(31,15), SHP_Area double(31,15), Major_Category char(254), Category char(254), Sub_Category char(254), Vintage char(254), CEEMap_Archetype char(254), BCBCOccupancy char(254), Part3_Part9 char(254), CT char(254), Neighbourhood char(254), Municipality char(254), RegionalDistrict char(254)
Note: electric meters outside parcel layer
Note: DeliveryPoint_Meters_unmatched [GEODATABASE_FILE]
DeliveryPoint_Meters_unmatched (writer GEODATABASE_FILE_2)
    attributes: OBJECTID integer, METER_NUMBER char(11), CUST_CLASS char(1), DPOID integer, DPSUBTYPECD integer, DPSUBTYPE char(40), TRANSFORMEROBJECTID integer, SERVICE_POINT_NUMBER double, ADDRESS char(40), EMAIL_ADDR char(100), LOCATION_DETAILS char(228), CONNECTIVITYCONFIRMEDDATE date, USAGEDATE double, ENDTIME date, KWH_USAGE double, KVAH_USAGE double, KVAH_DERIVED char(1), PFACTOR float, FABRIC_ID double(11,0), AFP_OID char(30), JUROL char(30), JURISDICTI char(50), JUR_NEIGH char(50), CREATDATE char(21), EFFECDATE char(21), EXPIRY_DAT char(21), PHOTO_LINK char(254), AREANAME char(50), SOURCE_ORI char(50), LOCALAREA char(50),
      SHP_Length double(31,15), SHP_Area double(31,15), Major_Category char(254), Category char(254), Sub_Category char(254), Vintage char(254), CEEMap_Archetype char(254), BCBCOccupancy char(254), Part3_Part9 char(254), CT char(254), Neighbourhood char(254), Municipality char(254), RegionalDistrict char(254)
